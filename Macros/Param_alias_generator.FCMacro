"""
This macro processes all spreadsheets that match a naming pattern for parameter
sheets. Several actions are performed:
	-- generates aliases for parameter values
	-- changes the display unit for the value cell if a unit is specified
	-- changes value cell coloration if certain tags are in the description

Alias generation:
	The parameter name is specified in column A. If the contents of a cell in
	column A matches a parameter name pattern, an alias is generated for the
	value cell which is in column B in the same row.

	This macro will only change the alias of a cell if it is blank or different.
	Note that if the alias is changed, any references to that alias in the part
	or body will revert to a cell reference rather than an alias.

Display unit:
	If the value cell in column B matches a pattern indicating that a specific
	unit was typed in when the value was entered, the display unit for that cell
	is changed to the typed unit.
	Only a few units are accepted at this time: mm|deg|°
	
Cell coloration:
	If the description cell in column C is prefixed with certain tags, the value
	cell in column B of the same row has its colors changed.
	[calculation] [calculated] [calc]  => light gray bg, black fg
	[fixed] [const] [constant]         => darg gray bg, white fg
	
Spreadsheets affected:
	This macro will operate on sheets with a certain name (case-insensitive):
		Params, Param, P, Params_<anything>, Param_<anything>, P_<anything>
	The macro will operate on all sheets matching the naming pattern.
	The macro may be run repeatedly on the spreadsheet.

Termination condition:
	Rows will be processed starting at row 1 and continuing until a	termination
	condition is met. Termination occurs after 10 consecutive rows all having
	the column A cell contants blank, or if the cell contents begin with two or
	more dashes:  ex/ --, --END--, --- END PARAMETERS ---, -----

Valid param names:
	Any column A cell contents having an invalid param name is skipped.
	A valid param name starts with a letter, has an optional underscore, and is
	followed by at least one letter, number, or underscore.

	Certain param names will be rejected, even if otherwise valid:
	Param or Params (case-insensitive) as these are often used as a header label
	One or two letters followed only by numbers as these are cell coordinates

Report:
	A short text report is emitted from the macro showing the changes, if any.

Author:
	Kerry S. Martin, martin@wild-wood.net   2024-09-21
"""
import FreeCAD
import re


# any of the following commonly used parameter sheet names may be used
RE_SHEET_NAMES = re.compile(r'^(?:P(?:_.*)?|PARAMs?(?:_.*)?|SPREADSHEET)$', re.IGNORECASE)

# number of consecutive blank rows to terminate alias generation
BLANK_ROWS = 10

# regex pattern to match valid param name
RE_NAME = re.compile(r'^[A-Z]_?[A-Z0-9_]+$', re.IGNORECASE)

# regex pattern to match param names in column A to reject
RE_NAME_REJECT = re.compile(r'^(?:[A-Z]{1,2}[0-9]+|PARAMs?)$', re.IGNORECASE)

# regex pattern to match termination marker
RE_TERMINATE = re.compile(r'^-{2,}')

# regex pattern to capture base value and unit from cell contents
# the contents must be a scientific number followed by a space then a alpha unit
RE_CONTENTS_UNIT = re.compile(r'^=?([-+0-9.eE]+)\s+(\S+)$')

# regex pattern to pull the column (letter) and row (number) from a cell reference
# ex/ AB12 -> group(1) = 'AB' = column, group(2) = '12' = row
RE_CELL_DISSECT = re.compile(r'^([A-Za-z]{1,2})([0-9]+)$')

# regex pattern to match a "[calculated]" tag in the description column
# description column follows the value column
# start the description with "[calculated]" to designate that the value is calculated
# and the cell will be shaded gray
RE_DESC_CALCULATED = re.compile(r"^'?\[CALC(?:ULATED|ULATION)?\]", re.IGNORECASE)

# regex pattern to match a "[fixed]" or "[constant]" tag in the description column
RE_DESC_FIXED = re.compile(r"^'?\[(?:FIXED|CONST|CONSTANT)]", re.IGNORECASE)

# regex pattern to match accepted display units
# add any additional display units that are needed to this regex
RE_ACCEPTED_DISPLAY_UNITS = re.compile(r"^(?:mm|deg|°)$")

# cell coloration constants
COLOR_BG_FIXED = (0.501960813999176,0.501960813999176,0.501960813999176,1.0)
COLOR_FG_FIXED = (1.0, 1.0, 1.0, 1.0)
COLOR_BG_CALC = (0.7529410123825073,0.7529410123825073,0.7529410123825073,1.0)
COLOR_FG_CALC = (0.0, 0.0, 0.0, 1.0)


def increment_column(cell, incr=1):
	"""Increment the column index without changing the row.
	
	Parameters
	----------
	cell : str
	  cell coordinate to increment (ex/ 'B15')
	incr : int {default=1}
	  amount to increment (+ increment, - decrement)
	
	Returns
	-------
	str
	  incremented cell coordinate (ex/ 'C15')
	"""

	next_cell = None

	if (m := RE_CELL_DISSECT.match(cell)) is not None:
		# grab the column and row
		my_col = m.group(1).upper()
		my_row = m.group(2)
		
		# calculate the zero-based numeric column index
		my_col_idx = ord(my_col[0])-ord('A')
		if len(my_col) > 1:
			# 2 character column index
			my_col_idx = (my_col_idx+1)*26 + ord(my_col[1])-ord('A')

		# adjust for increment/decrement
		my_col_idx = my_col_idx + incr
		
		if my_col_idx>=0 and my_col_idx<702:
			# determine the new alpha column index
			my_major_col = my_col_idx // 26
			if my_major_col > 0:
				my_col = chr(my_major_col-1+ord('A')) + chr((my_col_idx%26)+ord('A'))
			else:
				my_col = chr(my_col_idx+ord('A'))
		else:
			# outside of range 'A' to 'ZZ'
			my_col = None
		
		# the new coordinate is the alpha column and numeric row
		if my_col is not None:
			next_cell = my_col + my_row

	return next_cell


def is_color_close(c1, c2, tol=0.0001):
	""" Determines if two given color tuples are "close" (i.e. within tolerance)
	
	Parameters
	----------
	c1, c2 : tuple
	  color tuples ex/ (red, green, blue, opacity)
	tol : float {default = 0.0001}
	  tolerance, must be a non-negative number
	
	Returns
	-------
	bool
	  True if the colors match, False otherwise
	"""
	
	result = True   # unless changed to False
	
	if ( c1 is None ) or ( c2 is None ) or ( len(c1) != len(c2) ):
		result = False
	else:
		# if any value-pair is not within tolerance, then the result is False
		for i in range(len(c1)):
			if abs(c1[i]-c2[i])>tol:
				result = False
				break
	
	return result


def change_display_unit(param_sheet, value_cell):
	""" Change the display unit of the velue cell in the param sheet
	
	Parameters
	----------
	param_sheet : <Sheet object>
	value_cell : str
	  the cell coordinate (ex/ 'B15')
	
	Returns
	-------
	bool
	  True if a change was made, False otherwise
	"""

	result = False
	my_unit = param_sheet.getDisplayUnit(value_cell)

	if my_unit is None:
		my_contents = param_sheet.getContents(value_cell)
		m = RE_CONTENTS_UNIT.match(my_contents)

		if m is not None:
			my_unit = m.group(2)
			#my_value = m.group(1)

			if RE_ACCEPTED_DISPLAY_UNITS.match(my_unit):
				param_sheet.setDisplayUnit(value_cell, my_unit)
				#param_sheet.set(value_cell, my_value)  # KSM: disabled this for now
				result = True

	return result


def format_calculated_cell(param_sheet, value_cell):
	""" Change the coloration of the value cell if tagged in the description.
	
	Parameters
	----------
	param_sheet : <Sheet object>
	value_cell : str
	  the cell coordinates (ex/ 'B15')
	  the description cell is in the next column (ex/ 'C15')
	
	Returns
	-------
	bool
	  True if a change was made, False otherwise
	"""
	
	result = False
	# get the 'description' cell to the right of the value
	desc_cell = increment_column(value_cell)

	if desc_cell is not None:
		my_desc = param_sheet.getContents(desc_cell)

		if RE_DESC_CALCULATED.match(my_desc) is not None:
			# format as light gray
			c = param_sheet.getBackground(value_cell)
			if not is_color_close(c, COLOR_BG_CALC):
				param_sheet.setBackground(value_cell, COLOR_BG_CALC)
				param_sheet.setForeground(value_cell, COLOR_FG_CALC)
				result = True
			
		elif RE_DESC_FIXED.match(my_desc) is not None:
			# format as dark gray with white text
			c = param_sheet.getBackground(value_cell)
			if not is_color_close(c, COLOR_BG_FIXED):
				param_sheet.setBackground(value_cell, COLOR_BG_FIXED)
				param_sheet.setForeground(value_cell, COLOR_FG_FIXED)
				result = True
			
	return result
			

def change_alias(param_sheet, value_cell, alias, is_overwrite=False):
	""" Changes the alias assigned to the value cell
	
	Parameters
	----------
	param_sheet : <Sheet object>
	value_cell : str
	  the cell coordinates (ex/ 'B15')
	alias : str
	  the alias to which the value cell will be changed
	is_overwrite : bool {default = False}
	  if True, clear alias first the recalculate before changing alias
	
	Returns
	-------
	bool
	  True if the alias was changed, False otherwise
	"""
	
	result = True
	
	try:
		if is_overwrite:
			# clear the existing alias first, then recompute
			param_sheet.setAlias(value_cell, '')
			App.ActiveDocument.recompute()

		# set the new alias
		param_sheet.setAlias(value_cell, alias)

	except:
		# could be an invalid alias name or a duplicate alias
		result = False

	return result


def realias_sheet(param_sheet):
	""" Process all parameter alias names in the spreadsheet
	
	Parameters
	----------
	param_sheet : <Sheet object>

	Returns
	-------
	None
	"""
	row = 0
	blank_rows = 0
	had_change = False

	while True:

		# process each row until termination condition is met
		row += 1

		param_cell = f'A{row}'
		value_cell = f'B{row}'

		value_contents = None   # contents of the param_cell (may or may not be a param name)

		try:

			value_contents = param_sheet.get(param_cell)

			if len(value_contents) > 0:
				blank_rows = 0  # reset blank cell counter
			else:
				# blank cell
				blank_rows += 1
				if blank_rows >= BLANK_ROWS:
					# we have encountered the blank cell termination condition
					break

		except:

			# empty cell -> interpret as blank line
			blank_rows += 1
			if blank_rows >= BLANK_ROWS:
				# we have encountered the blank row termination condition
				break

			continue

		if RE_NAME_REJECT.match(value_contents):

			# skip any cell named simply "Param"... it is probably a header row
			# modify the RE_NAME_REJECT regex pattern to specify others to reject
			continue

		elif RE_NAME.match(value_contents):

			# we have a valid param name in column A
			# check for an existing alias
			alias = param_sheet.getAlias(value_cell)

			if alias is not None:
				if alias == value_contents:
					# already set, nothing to do
					pass
				else:
					# change it to the new name (assume it was already a valid value at some point)
					if change_alias(param_sheet, value_cell, value_contents, is_overwrite=True):
						had_change = True
						print(f'Changed the alias on cell {value_cell} to {value_contents} in sheet "{param_sheet.Label}"')
					else:
						print(f'Unable to change the alias on cell {value_cell} to {value_contents} in sheet "{param_sheet.Label}"')

			else:
				# for now, just set the alias
				if change_alias(param_sheet, value_cell, value_contents):
					had_change = True
					print(f'Added a new alias on cell {value_cell} as {value_contents} in sheet "{param_sheet.Label}"')
				else:
					print(f'Unable to add the new alias on cell {value_cell} as {value_contents} in sheet "{param_sheet.Label}"')
				
			# change the display unit then format gray if calculated
			if change_display_unit(param_sheet, value_cell):
				print(f'Changed the display unit on cell {value_cell} in sheet "{param_sheet.Label}"')
				had_change = True
			if format_calculated_cell(param_sheet, value_cell):
				print(f'Changed the formatting on cell {value_cell} in sheet "{param_sheet.Label}"')
				had_change = True
				
			continue
				

		elif RE_TERMINATE.match(value_contents):
			# we found the termination marker
			break

		else:
			continue

	if not had_change:
		print(f'No new changes were made to the spreadsheet aliases in sheet "{param_sheet.Label}"')
	
	else:
		param_sheet.touch()
		App.ActiveDocument.recompute()


# ------------------------------------------------------------------------------
# Main program entry point
# ------------------------------------------------------------------------------

# Find the parameter sheets and re-alias them
param_sheet = None

for obj in App.ActiveDocument.Objects:
	if obj.TypeId == 'Spreadsheet::Sheet' and RE_SHEET_NAMES.match(obj.Label):
		param_sheet = obj
		realias_sheet(param_sheet)

if param_sheet is None:
	print('No valid sheet name was found')
	


# Kerry S. Martin, martin@wild-wood.net, September 21, 2024
